########## Path Helper Macro ##########
# Macro for testing Path Helper features
#################################

import FreeCAD, FreeCADGui
from importlib import reload
import sys

print('###### Loading PathHelperFace #####')

try:
    # try import
    m_current_path = os.path.realpath(__file__)
    m_current_path = os.path.dirname(m_current_path)
    if not sys.path.__contains__(str(m_current_path) + "/PathHelperFaceDir"):
        sys.path.append(str(m_current_path) + "/PathHelperFaceDir")
    
    import PathHelperFaceGui
    reload(PathHelperFaceGui)
    import PathHelperFace
    reload(PathHelperFace)

except:
    print('Path Helper Face Macro Failed To Load')

panel = PathHelperFaceGui.PathHelperPanel()

if FreeCADGui.Control.activeDialog():
	FreeCAD.Console.PrintMessage("Dialog Panel currently open: Close it?")
FreeCADGui.Control.showDialog(panel)
